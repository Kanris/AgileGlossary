# Non-functional requirements document

# Specification: Specification Document
- Description: Requirements Document

## NON-F-REQ1
The terms should be kept in SQLite database
- Author: Alexey
- Status: Accepted

## NON-F-REQ2
Glossary should be cross-platform
- Status: Accepted
- Author: Alexey
- links to -> NON-F-REQ1
- links to -> NON-F-REQ3

## NON-F-REQ3
Glossary should be written in Java SE
- Author: Alexey
- Status: Accepted
