# Agile Glossary Functional Requirements Document

# Specification: Specification Document
- Description: Requirements Document

## REQ-1
The ability to view a list of terms
- Status: Accepted
- Priority: High
- Author: Alexey

## REQ-2
Terms properties consist of following fields
- Status: Accepted
- Priority: Middle
- Author: Alexey

### REQ-3
The term should be named
- Status: Accepted
- Priority: High
- Author: Alexey

### REQ-4
The term should have transcription
- Status: Accepted
- Priority: Middle
- Author: Alexey

### REQ-5
The term must have transcription
- Status: Accepted
- Priority: High
- Author: Alexey

## REQ-6
The ability to add new term
- Status: Accepted
- Priority: High
- Author: Alexey

## REQ-7
The ability to edit existed term
- Status: Accepted
- Priority: High
- Author: Alexey

## REQ-8
The ability to search terms
- Status: Accepted
- Priority: Low
- Author: Alexey

## REQ-9
The ability to remove existed term
- Status: Accepted
- Priority: High
- Author: Alexey
